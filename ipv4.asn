IPv4Address DEFINITIONS IMPLICIT TAGS ::= BEGIN

IPv4Address ::= OCTET STRING (SIZE(4))

IpLow16 ::= SEQUENCE {
	hi [0] INTEGER,
	lo [1] INTEGER
}

RawIpLow16 ::= OCTET STRING -- *.*.x.y; 4 bytes(1+1+2)

RawPrivateIpA ::= OCTET STRING -- 10.x.y.z;    5 bytes(1+1+3)
RawPrivateIpB ::= OCTET STRING -- 172.x.y.z;   5 bytes(1+1+3)

PrivateIpB ::= CHOICE {
	v0 [0] RawIpLow16, -- 172.16.x.y
	v1 [1] RawIpLow16, -- 172.17.x.y
	v2 [2] RawIpLow16, -- 172.18.x.y
	v3 [3] RawIpLow16, -- 172.19.x.y
	v4 [4] RawIpLow16, -- 172.20.x.y
	v5 [5] RawIpLow16, -- 172.21.x.y
	v6 [6] RawIpLow16, -- 172.22.x.y
	v7 [7] RawIpLow16, -- 172.23.x.y
	v8 [8] RawIpLow16, -- 172.24.x.y
	v9 [9] RawIpLow16, -- 172.25.x.y
	v10 [10] RawIpLow16, -- 172.26.x.y
	v11 [11] RawIpLow16, -- 172.27.x.y
	v12 [12] RawIpLow16, -- 172.28.x.y
	v13 [13] RawIpLow16, -- 172.29.x.y
	v14 [14] RawIpLow16, -- 172.30.x.y
	v15 [15] RawIpLow16 -- 172.31.x.y
}
RawPrivateIpC ::= OCTET STRING -- 192.168.x.y; 4 bytes(1+1+2)

-- 192.168.[0-23].y: 3 bytes(1+1+1)
-- 192.168.[24-255].y: 6 bytes(1+1+4)
PrivateIpC ::= CHOICE {
	v0 [0] INTEGER, -- 192.168.0.[0-255]
	v1 [1] INTEGER, -- 192.168.1.[0-255]
	v2 [2] INTEGER, -- 192.168.2.[0-255]
	v3 [3] INTEGER, -- 192.168.3.[0-255]
	v4 [4] INTEGER, -- 192.168.4.[0-255]
	v5 [5] INTEGER, -- 192.168.5.[0-255]
	v6 [6] INTEGER, -- 192.168.6.[0-255]
	v7 [7] INTEGER, -- 192.168.7.[0-255]
	v8 [8] INTEGER, -- 192.168.8.[0-255]
	v9 [9] INTEGER, -- 192.168.9.[0-255]
	v10 [10] INTEGER, -- 192.168.10.[0-255]
	v11 [11] INTEGER, -- 192.168.11.[0-255]
	v12 [12] INTEGER, -- 192.168.12.[0-255]
	v13 [13] INTEGER, -- 192.168.13.[0-255]
	v14 [14] INTEGER, -- 192.168.14.[0-255]
	v15 [15] INTEGER, -- 192.168.15.[0-255]
	v16 [16] INTEGER, -- 192.168.16.[0-255]
	v17 [17] INTEGER, -- 192.168.17.[0-255]
	v18 [18] INTEGER, -- 192.168.18.[0-255]
	v19 [19] INTEGER, -- 192.168.19.[0-255]
	v20 [20] INTEGER, -- 192.168.20.[0-255]
	v21 [21] INTEGER, -- 192.168.21.[0-255]
	v22 [22] INTEGER, -- 192.168.22.[0-255]
	v23 [23] INTEGER, -- 192.168.23.[0-255]
	vx [30] RawIpLow16 -- 192.168.$hi.$lo
}

IpV4 ::= CHOICE {
	cc0 [0] INTEGER, -- 192.168.0.[0-255],
	cc1 [1] INTEGER, -- 192.168.1.[0-255],
	cc2 [2] INTEGER, -- 192.168.2.[0-255],
	cc3 [3] INTEGER, -- 192.168.3.[0-255],
	cc4 [4] INTEGER, -- 192.168.4.[0-255],
	cc5 [5] INTEGER, -- 192.168.5.[0-255],
	cc6 [6] INTEGER, -- 192.168.6.[0-255],
	cc7 [7] INTEGER, -- 192.168.7.[0-255],
	cc8 [8] INTEGER, -- 192.168.8.[0-255],
	cc9 [9] INTEGER, -- 192.168.9.[0-255],
	cc10 [10] INTEGER, -- 192.168.10.[0-255],
	cc11 [11] INTEGER, -- 192.168.11.[0-255],
	cc12 [12] INTEGER, -- 192.168.12.[0-255],
	cc13 [13] INTEGER, -- 192.168.13.[0-255],
	cc14 [14] INTEGER, -- 192.168.14.[0-255],
	cc15 [15] INTEGER, -- 192.168.15.[0-255],
	lo [16] NULL, -- 127.0.0.1,
	cb [17] OCTET STRING, -- 172.[16-31].y.z,
	ca [18] OCTET STRING, -- 10.x.y.z,
	x [19] OCTET STRING, -- x.y.z.w
	z [20] NULL, -- 0.0.0.0
	l [21] OCTET STRING, -- 169.254.x.y
	m [22] OCTET STRING, -- 224.x.y.z
	b [23] NULL -- 255.255.255.255
}

TinyIpSetsC0 ::= BIT STRING {
	v1 (1), -- 192.168.0.1
	v2 (2), -- 192.168.0.2
	v3 (3), -- 192.168.0.3
	v4 (4), -- 192.168.0.4
	v5 (5), -- 192.168.0.5
	v6 (6), -- 192.168.0.6
	v7 (7) -- 192.168.0.7
}

TinyIpSetsC1 ::= BIT STRING {
	v1 (1), -- 192.168.1.1
	v2 (2), -- 192.168.1.2
	v3 (3), -- 192.168.1.3
	v4 (4), -- 192.168.1.4
	v5 (5), -- 192.168.1.5
	v6 (6), -- 192.168.1.6
	v7 (7) -- 192.168.1.7
}

SmallIpSetsC0 ::= BIT STRING {
	v1 (1), -- 192.168.0.1
	v2 (2), -- 192.168.0.2
	v3 (3), -- 192.168.0.3
	v4 (4), -- 192.168.0.4
	v5 (5), -- 192.168.0.5
	v6 (6), -- 192.168.0.6
	v7 (7), -- 192.168.0.7
	v8 (8), -- 192.168.0.8
	v9 (9), -- 192.168.0.9
	v10 (10), -- 192.168.0.10
	v11 (11), -- 192.168.0.11
	v12 (12), -- 192.168.0.12
	v13 (13), -- 192.168.0.13
	v14 (14), -- 192.168.0.14
	v15 (15) -- 192.168.0.15
}

END
